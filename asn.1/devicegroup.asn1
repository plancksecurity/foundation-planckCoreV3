/* This file is under GNU General Public License 3.0 */
/* see LICENSE.txt */

DEVICEGROUP
    { iso(1) org(3) dod(6) internet(1) private(4) enterprise(1) pEp (47878) sync(1) keysync(1) }

DEFINITIONS AUTOMATIC TAGS EXTENSIBILITY IMPLIED ::=

BEGIN

EXPORTS DeviceGroup-Protocol;
IMPORTS Version, Identity, IdentityList FROM PEP;

Beacon ::= NULL

HandshakeRequest ::= SEQUENCE {
    /* UUID of receiver, group UUID if grouped */
    partner-id     UTF8String  (SIZE(1..1024)) OPTIONAL,
    /* Group UUID of sender, if grouped */
    group-id       UTF8String  (SIZE(1..1024)) OPTIONAL
}

GroupKeys ::= SEQUENCE {
    /* UUID of receiver */
    partner-id     UTF8String  (SIZE(1..1024)) OPTIONAL,
    /* Group UUID of sender */
    group-id       UTF8String  (SIZE(1..1024)) OPTIONAL,
    ownIdentities IdentityList
}

GroupUpdate ::= SEQUENCE {
    ownIdentities IdentityList
}

/* TODO: narrow request to single key */
UpdateRequest ::= NULL 

/* for the tags see end of sync.fsm */

DeviceGroup-Protocol ::= SEQUENCE {
    header SEQUENCE {
        version     Version,
        sequence    INTEGER,  /* always increases */
        me          Identity, /* identity of the sender */
        state       INTEGER,  /* state the sender is in */
        devicegroup BOOLEAN
            /* signals if this message is coming from a device group member */
    },

    payload CHOICE {
        beacon [APPLICATION 2] Beacon,
        handshakeRequest [APPLICATION 3] HandshakeRequest,
        groupKeys [APPLICATION 4] GroupKeys,
        groupUpdate [APPLICATION 5] GroupUpdate,
        updateRequest [APPLICATION 6] UpdateRequest
    }
}

END
