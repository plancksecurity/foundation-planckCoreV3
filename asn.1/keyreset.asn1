-- This file is under BSD License 2.0

-- KeyReset protocol for p≡p
-- Copyleft 2016-2019 by p≡p foundation

-- Written by Volker Birk

KEYRESET
    { iso(1) org(3) dod(6) internet(1) private(4) enterprise(1) pEp(47878) distribution(2) keyreset(1) }

DEFINITIONS AUTOMATIC TAGS EXTENSIBILITY IMPLIED ::=

BEGIN

EXPORTS KeyReset;
IMPORTS Version, Identity, IdentityList, TID, Hash FROM PEP;

Commands ::= SEQUENCE {
    version Version,
    ident Identity,
    newkey Hash
}

KeyReset ::= CHOICE {
    commands [APPLICATION 1] Commands
}

END
