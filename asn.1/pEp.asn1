-- This file is under BSD License 2.0

-- Sync protocol for p≡p
-- Copyright (c) 2016-2021 p≡p foundation

-- Written by Volker Birk

PEP
    { iso(1) org(3) dod(6) internet(1) private(4) enterprise(1) pEp(47878) basic(0) }

DEFINITIONS AUTOMATIC TAGS EXTENSIBILITY IMPLIED ::=

BEGIN

EXPORTS Identity, IdentityList, TID, Hash, Version, Rating, PString,
        PStringList, PStringPair, PStringPairList, ISO639-1;

ISO639-1 ::= PrintableString(FROM ("a".."z")) (SIZE(2))
Hex ::= PrintableString(FROM ("A".."F" | "0".."9"))
Hash ::= Hex(SIZE(16..128)) -- 32bit Key ID to SHA512 in hex
PString ::= UTF8String  (SIZE(0..1024))
PStringList ::= SEQUENCE OF PString
TID ::= OCTET STRING (SIZE(16)) -- UUID version 4 variant 1

Identity ::= SEQUENCE {
    address     PString,
    fpr         Hash,
    user-id     PString,
    username    PString,
    comm-type   INTEGER (0..255),
    lang        ISO639-1,
    flags       INTEGER (0..65535)
}

IdentityList ::= SEQUENCE OF Identity

Version ::= SEQUENCE {
    major INTEGER (0..255) DEFAULT 1,
    minor INTEGER (0..255) DEFAULT 2
}

Rating ::= ENUMERATED { 
    -- no color

    cannot-decrypt (1),
    have-no-key (2),
    unencrypted (3),
    unreliable (5),

    b0rken (-2),

    -- yellow

    reliable (6),

    -- green

    trusted (7),
    trusted-and-anonymized (8),
    fully-anonymous (9), 

    -- red

    mistrust (-1),
    under-attack (-3)
}

PStringPair ::= SEQUENCE {
    key      PString,
    value    PString
}

PStringPairList ::= SEQUENCE OF PStringPair

END
