/* This file is under GNU General Public License 3.0 */
/* see LICENSE.txt */

SYNC

DEFINITIONS AUTOMATIC TAGS EXTENSIBILITY IMPLIED ::=

BEGIN

IMPORTS DeviceGroup-Protocol FROM DEVICEGROUP;

Sync-Protocols ::= CHOICE {
    deviceGroup [APPLICATION 1] DeviceGroup-Protocol
}

END
